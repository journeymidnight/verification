JMD-STORAGE-MIB DEFINITIONS ::= BEGIN

-- *****************************************************************
--
-- IMPORTS section
--
-- *****************************************************************
IMPORTS
  NOTIFICATION-TYPE, MODULE-IDENTITY, OBJECT-TYPE, enterprises, Integer32,
Gauge32, IpAddress, Counter64 FROM SNMPv2-SMI
  MODULE-COMPLIANCE, OBJECT-GROUP, NOTIFICATION-GROUP FROM SNMPv2-CONF
;

jmdStorageMIB  MODULE-IDENTITY
  LAST-UPDATED "201711270000Z" -- UTC format is YYMMDDHHmmZ
  ORGANIZATION "EKing Inc."
  CONTACT-INFO "Dongmao Zhang, dmao.zhang@haihangyun.com"
  DESCRIPTION
    "JMD Storage enterprise-specific MIB tree."
    REVISION "201711270000Z"
    DESCRIPTION "Initial draft 0.2"
  ::= { enterprises 51052} 

jmdSysInfoGroup OBJECT IDENTIFIER ::= { jmdStorageMIB 1 }


jmdStorageNotifications OBJECT IDENTIFIER ::= { jmdStorageMIB 2 }
jmdStorageNotificationPrefix  OBJECT IDENTIFIER
                                  ::= { jmdStorageNotifications 1 }
jmdStorageNotificationObjects OBJECT IDENTIFIER
                                  ::= { jmdStorageNotifications 2 }



resourceID OBJECT-TYPE
  SYNTAX OCTET STRING
  MAX-ACCESS read-only
  STATUS current
  DESCRIPTION
    "Cluster's uniq ID"
  ::= { jmdSysInfoGroup 1 }

totalVolume OBJECT-TYPE
  SYNTAX OCTET STRING
  MAX-ACCESS read-only
  STATUS current
  DESCRIPTION
    "Cluster's total volume"
  ::= { jmdSysInfoGroup 2 }

freeVolume OBJECT-TYPE
  SYNTAX OCTET STRING
  MAX-ACCESS read-only
  STATUS current
  DESCRIPTION
    "Cluster's free volume"
  ::= { jmdSysInfoGroup 3 }

state OBJECT-TYPE
  SYNTAX OCTET STRING
  MAX-ACCESS read-only
  STATUS current
  DESCRIPTION
    "Cluster's status"
  ::= { jmdSysInfoGroup 4 }


-- ****************
-- Disk Info Table 
-- ****************

clusterDiskTable OBJECT-TYPE
    SYNTAX      SEQUENCE OF DiskEntry
    MAX-ACCESS  not-accessible
    STATUS      current
    DESCRIPTION
    "This table merely contains a table of ALL disks of storage"
    ::= { jmdSysInfoGroup 5 }


diskEntry OBJECT-TYPE
    SYNTAX      DiskEntry
    MAX-ACCESS  not-accessible
    STATUS      current
    DESCRIPTION
    "A row describing a given working group"
    INDEX { jmdDiskName }
    ::= {clusterDiskTable 1 }

DiskEntry ::= SEQUENCE {
    jmdDiskName             OCTET STRING,
    jmdHostName             OCTET STRING,
    jmdHostAddress          OCTET STRING,
    jmdUsedKb               Gauge32,
    jmdKb                   Gauge32,
    jmdUp                   Gauge32
}

jmdDiskName OBJECT-TYPE
    SYNTAX      OCTET STRING (SIZE(0..64))
    MAX-ACCESS  read-only
    STATUS      current
    DESCRIPTION
    "Disk's unique number"
    ::= { diskEntry 1 }

jmdHostName OBJECT-TYPE
    SYNTAX      OCTET STRING
    MAX-ACCESS  read-only
    STATUS      current
    DESCRIPTION
    "The hostname on which the disk is"
    ::= { diskEntry 2 }


jmdHostAddress OBJECT-TYPE
    SYNTAX      OCTET STRING
    MAX-ACCESS  read-only
    STATUS      current
    DESCRIPTION
    "IP of the host"
    ::= { diskEntry 3 }

jmdUsedKb OBJECT-TYPE
    SYNTAX      Gauge32
    MAX-ACCESS  read-only
    STATUS      current
    DESCRIPTION
    "Used bytes of the disk"
    ::= { diskEntry 4 }

jmdKb OBJECT-TYPE
    SYNTAX      Gauge32
    MAX-ACCESS  read-only
    STATUS      current
    DESCRIPTION
    "Total Bytes of the disk"
    ::= { diskEntry 5 }

jmdUp OBJECT-TYPE
    SYNTAX      Gauge32
    MAX-ACCESS  read-only
    STATUS      current
    DESCRIPTION
    "Status of the disk. if the value is not 1, this means the disk is offline"
    ::= { diskEntry 6 }


-- ****************
-- Fan Info Table 
-- ****************

fanInfoTable OBJECT-TYPE    -- the table object
  SYNTAX SEQUENCE OF FanInfoEntry
  MAX-ACCESS not-accessible
  STATUS current
  DESCRIPTION
    "Fan information table."
  ::= { jmdSysInfoGroup 6 }

fanInfoEntry OBJECT-TYPE    -- the entry object
  SYNTAX FanInfoEntry
  MAX-ACCESS not-accessible
  STATUS current
  DESCRIPTION
    "Fan information table."
  INDEX { fanSlot }
  ::= { fanInfoTable 1 }

FanInfoEntry ::=          -- the SEQUENCE statement
  SEQUENCE {
    fanSlot    OCTET STRING,
    fanRpm     OCTET STRING,
    fanState    OCTET STRING
}

fanSlot OBJECT-TYPE
  SYNTAX OCTET STRING(SIZE(0..32))
  MAX-ACCESS read-only
  STATUS current
  DESCRIPTION
    "FAN slot."
  ::= { fanInfoEntry 1 }

fanRpm OBJECT-TYPE
  SYNTAX OCTET STRING
  MAX-ACCESS read-only
  STATUS current
  DESCRIPTION
    "FAN RPm."
  ::= { fanInfoEntry 2 }

fanState OBJECT-TYPE
  SYNTAX OCTET STRING
  MAX-ACCESS read-only
  STATUS current
  DESCRIPTION
    "FAN state."
  ::= { fanInfoEntry 3 }




-- ****************
-- power Info Table 
-- ****************

powerInfoTable OBJECT-TYPE    -- the table object
  SYNTAX SEQUENCE OF PowerInfoEntry
  MAX-ACCESS not-accessible
  STATUS current
  DESCRIPTION
    "power information table."
  ::= { jmdSysInfoGroup 7 }

powerInfoEntry OBJECT-TYPE    -- the entry object
  SYNTAX PowerInfoEntry
  MAX-ACCESS not-accessible
  STATUS current
  DESCRIPTION
    "power information table."
  INDEX { powerSlot }
  ::= { powerInfoTable 1 }

PowerInfoEntry ::=          -- the SEQUENCE statement
  SEQUENCE {
    powerSlot    OCTET STRING,
    powerState    OCTET STRING
}

powerSlot OBJECT-TYPE
  SYNTAX OCTET STRING(SIZE(0..32))
  MAX-ACCESS read-only
  STATUS current
  DESCRIPTION
    "power slot."
  ::= { powerInfoEntry 1 }

powerState OBJECT-TYPE
  SYNTAX OCTET STRING
  MAX-ACCESS read-only
  STATUS current
  DESCRIPTION
    "power state."
  ::= { powerInfoEntry 2 }


-- ****************
-- CPU temperature Table 
-- ****************

cpuTemperatureTable OBJECT-TYPE    -- the table object
  SYNTAX SEQUENCE OF CPUTemperatureEntry
  MAX-ACCESS not-accessible
  STATUS current
  DESCRIPTION
    "power information table."
  ::= { jmdSysInfoGroup 8 }

cpuTemperatureEntry OBJECT-TYPE    -- the entry object
  SYNTAX CPUTemperatureEntry
  MAX-ACCESS not-accessible
  STATUS current
  DESCRIPTION
    "power information table."
  INDEX { cpuSlot }
  ::= { cpuTemperatureTable 1 }

CPUTemperatureEntry ::=          -- the SEQUENCE statement
  SEQUENCE {
    cpuSlot    OCTET STRING,
    cpuTemperature OCTET STRING
}

cpuSlot OBJECT-TYPE
  SYNTAX OCTET STRING(SIZE(0..32))
  MAX-ACCESS read-only
  STATUS current
  DESCRIPTION
    "power slot."
  ::= { cpuTemperatureEntry 1 }

cpuTemperature OBJECT-TYPE
  SYNTAX OCTET STRING
  MAX-ACCESS read-only
  STATUS current
  DESCRIPTION
    "Cpu temperauture in centi degree"
  ::= { cpuTemperatureEntry 2 }



-- ****************
-- Network Interface Table 
-- ****************

networkInterfaceTable OBJECT-TYPE    -- the table object
  SYNTAX SEQUENCE OF NetworkInterfaceEntry
  MAX-ACCESS not-accessible
  STATUS current
  DESCRIPTION
    "network interface table."
  ::= { jmdSysInfoGroup 9 }

networkInterfaceEntry OBJECT-TYPE    -- the entry object
  SYNTAX NetworkInterfaceEntry
  MAX-ACCESS not-accessible
  STATUS current
  DESCRIPTION
    "network interface table."
  INDEX { jmdInterfaceSlot }
  ::= { networkInterfaceTable 1 }

NetworkInterfaceEntry ::=          -- the SEQUENCE statement
  SEQUENCE {
    jmdInterfaceSlot    OCTET STRING,
    jmdInterfaceStat    OCTET STRING
}

jmdInterfaceSlot OBJECT-TYPE
  SYNTAX OCTET STRING(SIZE(0..32))
  MAX-ACCESS read-only
  STATUS current
  DESCRIPTION
    "power slot."
  ::= { networkInterfaceEntry 1 }

jmdInterfaceStat OBJECT-TYPE
  SYNTAX OCTET STRING
  MAX-ACCESS read-only
  STATUS current
  DESCRIPTION
    "Cpu temperauture in centi degree"
  ::= { networkInterfaceEntry 2 }

-- *****************************************************************
--
-- NOTIFICATION TYPE definition section
--
-- *****************************************************************

nodeIsDownEvent OBJECT-TYPE
  SYNTAX OCTET STRING
  MAX-ACCESS read-only
  STATUS current
  DESCRIPTION
    "Node becomes bad."
  ::= { jmdStorageNotificationObjects 1 }

clusterHealthEvent OBJECT-TYPE
  SYNTAX OCTET STRING
  MAX-ACCESS read-only
  STATUS current
  DESCRIPTION
    "Internal error detected for cluster."
  ::= { jmdStorageNotificationObjects 2 }

clusterSpaceUsageHighEvent OBJECT-TYPE
  SYNTAX OCTET STRING
  MAX-ACCESS read-only
  STATUS current
  DESCRIPTION
    "Cluster space usage is high."
  ::= { jmdStorageNotificationObjects 3 }

nodeCpuLoadHighEvent OBJECT-TYPE 
  SYNTAX OCTET STRING
  MAX-ACCESS read-only
  STATUS current
  DESCRIPTION
    "node's cpu load is high"
  ::= { jmdStorageNotificationObjects 4 }

nodeCpuTempHighEvent OBJECT-TYPE
  SYNTAX OCTET STRING
  MAX-ACCESS read-only
  STATUS current
  DESCRIPTION
    "node's cpu temperature is high"
  ::= { jmdStorageNotificationObjects 5 }


nodeMemHighEvent OBJECT-TYPE
  SYNTAX OCTET STRING
  MAX-ACCESS read-only
  STATUS current
  DESCRIPTION
    "node's memory usage is high"
  ::= { jmdStorageNotificationObjects 6 }

nodeTraficHighEvent OBJECT-TYPE
  SYNTAX OCTET STRING
  MAX-ACCESS read-only
  STATUS current
  DESCRIPTION
    "node's network trafic is high"
  ::= { jmdStorageNotificationObjects 7 }

nodePowerDownEvent OBJECT-TYPE
  SYNTAX OCTET STRING
  MAX-ACCESS read-only
  STATUS current
  DESCRIPTION
    "one of the power module is down"
  ::= { jmdStorageNotificationObjects 8}

clusterDiskDownEvent OBJECT-TYPE
  SYNTAX OCTET STRING
  MAX-ACCESS read-only
  STATUS current
  DESCRIPTION
    "some disk of cluster is down"
  ::= { jmdStorageNotificationObjects 9}

---  

nodeIsDownNotif NOTIFICATION-TYPE
  OBJECTS { nodeIsDownEvent }
  STATUS current
  DESCRIPTION
    "Node becomes bad."
  ::= { jmdStorageNotificationPrefix 1 }


clusterHealthNotif NOTIFICATION-TYPE
  OBJECTS { clusterHealthEvent }
  STATUS current
  DESCRIPTION
    "Internal error detected for cluster."
  ::= { jmdStorageNotificationPrefix 2 }


clusterSpaceUsageHighNotif NOTIFICATION-TYPE
  OBJECTS { clusterSpaceUsageHighEvent }
  STATUS current
  DESCRIPTION
    "Cluster space usage is high."
  ::= { jmdStorageNotificationPrefix 3 }

nodeCpuLoadHighNotif NOTIFICATION-TYPE
  OBJECTS { nodeCpuLoadHighEvent }
  STATUS current
  DESCRIPTION
    "node cpu is high."
  ::= { jmdStorageNotificationPrefix 4 }

nodeCpuTempHighNotif NOTIFICATION-TYPE
  OBJECTS { nodeCpuTempHighEvent }
  STATUS current
  DESCRIPTION
    "node cpu temperature is High"
  ::= { jmdStorageNotificationPrefix 5 }

nodeMemHighNotif NOTIFICATION-TYPE
  OBJECTS { nodeMemHighEvent }
  STATUS current
  DESCRIPTION
    "node memory is high."
  ::= { jmdStorageNotificationPrefix 6 }

nodeTraficHighNotif NOTIFICATION-TYPE
  OBJECTS { nodeTraficHighEvent }
  STATUS current
  DESCRIPTION
    "node's trafic is high."
  ::= { jmdStorageNotificationPrefix 7 }

nodePowerDownNotif NOTIFICATION-TYPE
  OBJECTS { nodePowerDownEvent }
  STATUS current
  DESCRIPTION
    "node's trafic is high."
  ::= { jmdStorageNotificationPrefix 8 }

clusterDiskDownNotif NOTIFICATION-TYPE
  OBJECTS { clusterDiskDownEvent }
  STATUS current
  DESCRIPTION
    "cluster disk is down"
  ::= { jmdStorageNotificationPrefix 9 }

END
